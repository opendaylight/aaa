module aaa-idmlight {
  yang-version 1;
  namespace "config:aaa:authn:idmlight";
  prefix "aaa-idmlight";
    organization "OpenDayLight";

    import config { prefix config; revision-date 2013-04-05; }
    import opendaylight-md-sal-binding { prefix mdsal; revision-date 2013-10-28; }

    contact "saichler@gmail.com";

    revision 2015-12-04 {
        description
            "Initial revision.";
    }

    identity aaa-idmlight {
        base config:module-type;
        config:java-name-prefix AAAIDMLight;
    }

    augment "/config:modules/config:module/config:configuration" {
        case aaa-idmlight {
            when "/config:modules/config:module/config:type = 'aaa-idmlight'";
        }
    }

}
