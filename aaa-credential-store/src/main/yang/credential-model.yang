/*
 * Copyright (c) 2015 Hewlett-Packard Development Company, L.P. and others.  All rights reserved.
 *
 * This program and the accompanying materials are made available under the
 * terms of the Eclipse Public License v1.0 which accompanies this distribution,
 * and is available at http://www.eclipse.org/legal/epl-v10.html
 */
module credential-model {
    yang-version 1;
    namespace "urn:opendaylight:params:xml:ns:yang:aaa:credential-store";
    prefix "cs";

    description
       "The model defines the strcture for storing security credential and
       allows for defining multiple types of credentials";

    revision "2015-02-18" {
       description
          "Initial revision.";
    }

    identity base-credential-type {
       description
          "Credential base type.  All credential identities must be derived
          from this type.";
    }
    
    container credentials {
       list credential {
          key "type";

          leaf type {
             type identityref {
                base base-credential-type;
             }
          }

          choice key-data {
          }
       }
    }
}
