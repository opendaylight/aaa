module aaa-cassandra-store {
  yang-version 1;
  namespace "urn:opendaylight:params:xml:ns:yang:controller:config:aaa:cassandra:store";
  prefix "aaa-cassandra-store";
    organization "OpenDayLight";

    import config { prefix config; revision-date 2013-04-05; }
    import opendaylight-md-sal-binding { prefix mdsal; revision-date 2013-10-28; }

    contact "saichler@gmail.com";

    revision 2015-11-28 {
        description
            "Initial revision.";
    }

    identity aaa-cassandra-store {
            base config:module-type;
            config:java-name-prefix AAACassandraStore;
    }

    augment "/config:modules/config:module/config:configuration" {
                case aaa-cassandra-store {
                    when "/config:modules/config:module/config:type = 'aaa-cassandra-store'";
                }
            }

}
