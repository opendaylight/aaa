/*
Copyright (c) 2015 Inocybe Technology All rights reserved.

This program and the accompanying materials are made available under the
terms of the Eclipse Public License v1.0 which accompanies this distribution,
and is available at http://www.eclipse.org/legal/epl-v10.html INTERNAL
*/

module aaa-cert-rpc {
    yang-version 1;
    namespace "urn:opendaylight:yang:aaa:cert:rpc";
    prefix "aaa-cert-rpc";

    description
        "defination of node certificate grouping and Rpc calls of certificate manipulation";

    contact
        "melserngawy@inocybe.com";

    revision "2015-12-15" {
        description
            "Initial revision.";
    }

    rpc getODLCertificate {
        description
            "Get the ODL keystore certificate";
        output {
           leaf odl-cert {
               type string;
           }
        }
    }

    rpc getODLCertificateReq {
        description
            "Generate a certificate request from the ODL keystore to be signed by a CA";
        output {
           leaf odl-cert-req {
               type string;
           }
        }
    }

    rpc setODLCertificate {
        description
            "The certificate should be generated based on
            a certificate request generated from the ctl.jks
            keystore otherwise the certificated will not be added to ctl keystore";
        input {
            leaf odl-cert-alias {
                type string;
            }
           leaf odl-cert {
               type string;
           }
        }
    }

    rpc setNodeCertificate {
        description
            "Set the certificate of the network node that will communicate with opendaylight through TLS connection";
        input {
           leaf node-alias {
               type string;
           }
           leaf node-cert {
               type string;
           }
        }
    }

    rpc getNodeCertificate {
        description
            "Get the network node certificate based on node alias";
        input {
           leaf node-alias {
               type string;
           }
        }
        output {
            leaf node-cert {
                type string;
            }
        }
    }
}
