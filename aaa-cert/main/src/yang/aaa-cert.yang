module aaa-cert {
    yang-version 1;
    namespace "urn:opendaylight:params:xml:ns:yang:aaa:cert";
    prefix "aaa-cert";

    import config {
        prefix config;
        revision-date 2013-04-05;
    }

    import opendaylight-md-sal-binding {
        prefix mdsal;
        revision-date 2013-10-28;
    }

    description
        "Service definition for aaa certificate";

    revision "2015-11-26" {
        description
            "Initial revision.";
    }

    identity aaa-cert {
        base config:module-type;
        config:java-name-prefix IaaaCertProvider;
    }

    augment "/config:modules/config:module/config:configuration" {
        case aaa-cert {
            when "/config:modules/config:module/config:type = 'aaa-cert'";
            container data-broker {
                uses config:service-ref {
                    refine type {
                        mandatory true;
                        config:required-identity md-sal-binding:binding-broker-osgi-registry;
                    }
                }
            }
        }
    }
}
