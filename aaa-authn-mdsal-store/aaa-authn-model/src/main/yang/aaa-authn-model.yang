module aaa-authn-model {
	yang-version 1;
	namespace "urn:aaa:yang:authn:claims";
  prefix "authn";
    organization "TBD";

    contact "wdec@cisco.com";

    revision 2014-10-29 {
        description
            "Initial revision.";
    }


//Main module begins

// Following container provides the AuthN Claims data-structure

  container tokencache {
    config false;
    list claims {
      key "userId token";

      leaf token {
        type string;
        description "Token";
      }

      leaf clientId {
        type string;
        description "id of the authorized client, or null if anonymous";
      }
      leaf userId {
        type string;
        description "Unique user-id. User IDs are system-created";
      }
      leaf user {
        type string;
        description "User name";
      }
      leaf domain {
        type string;
        description "Fully-qualified domain name";
      }
      leaf-list roles {
        type string;
        description "Assigned user roles";
      }

        leaf expiration {

          type int64;
          description "Expiration milliseconds since start of UTC epoch";
        }

      leaf timestamp {

        type uint64;
      }
    }
  }
}
