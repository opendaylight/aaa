module aaa-authn-mdsal-store-cfg {

    yang-version 1;
    namespace "config:aaa:authn:mdsal:store";
    prefix "aaa-authn-store-cfg";

    description
        "This module contains the base YANG definitions for
        AuthN MD-SAL backed data cache implementation.";

    revision "2014-10-31" {
        description
            "Initial revision.";
    }

    container mdsal-config {
           leaf timeToLive {
             description "Time to live for tokens. When set to 0 = never expire";
             type uint64;
             default 360000;
           }
           leaf timeToWait {
             description "Time to wait for future from data store. 10 by default = never expire";
             type uint16;
             default 10;
           }
       }

}
