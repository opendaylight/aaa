module aaa-password-service-config {
    yang-version 1;
    namespace "urn:opendaylight:aaa:password:service:config";
    prefix "aaa-password-service-config";
    organization "OpenDaylight";

    contact "ryandgoulding@gmail.com";

    revision "2017-06-19" {
        description "Initial password service configuration.";
    }

    container password-service-config {

        leaf algorithm {
            type string;
            default "SHA-512";
            description "The algorithm utilized for aaa-password-service hashing.";
        }

        leaf iterations {
            type int32;
            default 20000;
            description "The number of times to hash.";
        }

        leaf private-salt {
            type string;
            description "The private salt for password hashing.";
        }

    }
}
