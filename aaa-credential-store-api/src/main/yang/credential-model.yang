/*
 * Copyright (c) 2015 Hewlett-Packard Development Company, L.P. and others.  All rights reserved.
 *
 * This program and the accompanying materials are made available under the
 * terms of the Eclipse Public License v1.0 which accompanies this distribution,
 * and is available at http://www.eclipse.org/legal/epl-v10.html
 */
module credential-store {
    namespace "urn:opendaylight:params:xml:ns:yang:aaa:credential-store";
    prefix "cs";

    description "Defines and extensible model for storing various types of security credentials.";

    revision "2015-02-26" { description "Initial revision."; }

    identity credential-type {
        status deprecated;
        description
          "Credential base type.  All credential types must be derived from this identity.";
    }

    typedef credential-type-ref {
        status deprecated;
        description "reference to an entry in the credential store based on id.";
        type instance-identifier;
    }

    container credential-store {
        status deprecated;
        list credential {
            key "id";

            leaf id {
                description "Unique identifier for this credential entry.";
                type string;
            }

            leaf type {
                description "The type of credential represented in this entry.";
                type identityref {
                    base credential-type;
                }
            }

            choice value {
                description "Extension point. Contains the data specific to the credential type.";
            }
        }
    }
}
