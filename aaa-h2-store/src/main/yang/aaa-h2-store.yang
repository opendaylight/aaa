module aaa-h2-store {
  yang-version 1;
  namespace "config:aaa:authn:h2:store";
  prefix "aaa-h2-store";
    organization "OpenDayLight";

    import config { prefix config; revision-date 2013-04-05; }
    import opendaylight-md-sal-binding { prefix mdsal; revision-date 2013-10-28; }

    contact "saichler@gmail.com";

    revision 2015-11-28 {
        description
            "Initial revision.";
    }

    identity aaa-h2-store {
        base config:module-type;
        config:java-name-prefix AAAH2Store;
    }

    augment "/config:modules/config:module/config:configuration" {
        case aaa-h2-store {
            when "/config:modules/config:module/config:type = 'aaa-h2-store'";
        }
    }

}
