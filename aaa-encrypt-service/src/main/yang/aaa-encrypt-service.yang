module aaa-encrypt-service {
  yang-version 1;
  namespace "config:aaa:authn:encrypt:service";
  prefix "aaa-encrypt-service";
    organization "OpenDayLight";

    import config { prefix config; revision-date 2013-04-05; }
    import opendaylight-md-sal-binding { prefix mdsal; revision-date 2013-10-28; }

    contact "saichler@gmail.com";

    revision 2016-04-26 {
        description
            "Initial revision.";
    }

    identity aaa-encrypt-service {
        base config:module-type;
        config:java-name-prefix AAAEncryptService;
    }

    augment "/config:modules/config:module/config:configuration" {
        case aaa-encrypt-service {
            when "/config:modules/config:module/config:type = 'aaa-encrypt-service'";
            leaf encrypt-key {
                description "Encryption key";
                type string;
            }
            leaf encrypt-salt {
                description "Encryption key salt";
                type string;
            }
            leaf encrypt-tag {
                description "Encryption tag to mark an encrypted string";
                type string;
            }
            leaf encrypt-method {
                description "The encryption method to use";
                type string;
            }
            leaf encrypt-type {
                description "The encryption type";
                type string;
            }
            leaf encrypt-iteration-count {
                type int32;
            }
            leaf encrypt-key-length {
                type int32;
            }
            leaf cipher-transforms {
                type string;
            }
        }
    }

}
