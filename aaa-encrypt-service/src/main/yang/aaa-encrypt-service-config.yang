module aaa-encrypt-service-config {
  yang-version 1;
  namespace "config:aaa:authn:encrypt:service:config";
  prefix "aaa-encrypt-service-config";
    organization "OpenDayLight";

    contact "melserngawy@inocybe.ca";

    revision 2016-09-15 {
        description
        "Initial revision.";
    }

    container aaa-encrypt-service-config {
        leaf encrypt-key {
            description "Encryption key";
            type string;
        }
        leaf encrypt-salt {
            description "Encryption key salt";
            type string;
        }
        leaf encrypt-tag {
            description "Encryption tag to mark an encrypted string";
            type string;
        }
        leaf encrypt-method {
            description "The encryption method to use";
            type string;
        }
        leaf encrypt-type {
            description "The encryption type";
            type string;
        }
        leaf encrypt-iteration-count {
            description "Number of iterations that will be used by the key";
            type int32;
        }
        leaf encrypt-key-length {
            description "Key length";
            type int32;
        }
        leaf cipher-transforms {
            description "cipher transformation type ex: AES/CBC/PKCS5Padding (128)";
            type string;
        }
    }

}
